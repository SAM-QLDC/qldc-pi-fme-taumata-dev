FME workspace agol.fmw

Bookmark: extract: agol layers
Creator
    GEOMTYPE = Geometry Object
    NUM = 1
    CREATED -> _Three_Waters_Assets [INITIATOR]
    CREATED -> FeatureReader [INITIATOR]
_Three_Waters_Assets: FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Only Use Result
    COMBINE_GEOM = Use Result
    FEATURETYPES = Stormwater Lateral Stormwater Main Wastewater Lateral Wastewater Main Water Supply Lateral Water Supply Main
    FORMAT = ARCGISONLINEFEATURES
    INTERACT = NONE
    ORDER_RESULTS = No
    OUTPUT_FEATURES_DISPLAY = Schema and Data Features
FeatureReader
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Only Use Result
    COMBINE_GEOM = Use Result
    FORMAT = ARCGISONLINEFEATURES
    INTERACT = NONE
    ORDER_RESULTS = No
    OUTPUT_FEATURES_DISPLAY = Schema and Data Features
