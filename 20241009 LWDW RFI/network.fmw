FME workspace network.fmw

Parameters:
- DestDataset_CSV2 = C:\Github\qldc-pi-fme-taumata-dev\20241009 LWDW RFI   # Destination CSV (Comma Separated Value) Folder

Writers:
- CSV2_1: CSV2 to $(DestDataset_CSV2)

Bookmark: datetime
Creator
    GEOMTYPE = Geometry Object
    NUM = 1
    CREATED -> origin_utc
origin_utc: DateTimeStamper
    DATETIME_ATTR = origin_utc
    INCLUDE_FRAC_SECONDS = NO
    INCLUDE_OFFSET = NO
    STAMP_TYPE = datetime
    TIMEZONE = utc
    -> Junction_7
Junction_7
    -> Junction_8

Bookmark: extract: 3 water pipes
Junction_8
    -> _Three_Waters_Assets [INITIATOR]
Note: _Three_Waters_Assets [FeatureReader] / Reading: / Reader: / Dataset: <not set> / Coordinate System: <not set> / Constraints: / Feature Types to Read: "Stormwater Lateral" "Stormwater Main" "Wastewater Lateral" "Wastewater Main" "Water Supply Lateral" "Water Supply Main" / Feature Type Separator: SPACE / WHERE Clause: <not set> / Spatial Filter: <No Spatial Filter> / Max Features to Read: <not set> / Schema/Data Features: / Features to Read: Schema and Data Features / Output: / Output Ports: / [x] One per Feature Type Regenerate: On Reader Parameter change / Attribute and Geometry Handling: / Accumulation Mode: Merge Initiator and Result / Conflict Resolution: Use Result / Ignore Nulls: No / Geometry: Use Result / <Generic> Port: / Attributes to Expose: <not set> / ARCGISONLINEFEATURES Resolve Domains: No / ARCGISONLINEFEATURES Feature Service: Queenstown Lakes District Council Open Data/Three Waters Assets(a99d1860d32f44fbb025142a364d0458) / ARCGISONLINEFEATURES ArcGIS Online Connection: hywell Esri ArcGIS Online / ARCGISONLINEFEATURES Features Per Request: 1000 / ARCGISONLINEFEATURES Additional Attributes to Expose: <not set>
_Three_Waters_Assets: FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Stormwater Lateral Stormwater Main Wastewater Lateral Wastewater Main Water Supply Lateral Water Supply Main
    FORMAT = ARCGISONLINEFEATURES
    INTERACT = NONE
    ORDER_RESULTS = No
    OUTPUT_FEATURES_DISPLAY = Schema and Data Features
    Stormwater Lateral -> AttributeCreator_3
    Stormwater Main -> AttributeCreator_6
    Wastewater Lateral -> AttributeCreator
    Wastewater Main -> AttributeCreator_2
    Water Supply Lateral -> AttributeCreator_4
    Water Supply Main -> AttributeCreator_5
AttributeCreator_3
    ATTR_TABLE = SET_TO system (buffer) = SW
    -> Junction
AttributeCreator
    ATTR_TABLE = SET_TO system (buffer) = WW
    -> Junction
AttributeCreator_4
    ATTR_TABLE = SET_TO system (buffer) = WS
    -> Junction
Junction
    -> Junction_2
AttributeCreator_6
    ATTR_TABLE = SET_TO system (buffer) = SW
    -> Junction_3
AttributeCreator_5
    ATTR_TABLE = SET_TO system (buffer) = WS
    -> Junction_3
AttributeCreator_2
    ATTR_TABLE = SET_TO system (buffer) = WW
    -> Junction_3
Junction_3
    -> Junction_4

Bookmark: transform: merge key fields
Junction_2
    -> AttributeKeeper
Junction_4
    -> AttributeKeeper
AttributeKeeper
    CREATE_BULK_MODE_FEATURES = NO
    KEEP_ATTRS = OBJECTID,ASSETTYPE,COMPKEY,PIPELEN,OWN,SERVSTAT,system,origin_utc
    -> Tester
Note: Tester [Tester] / Test Clauses: Left ValueOperatorRight Value@Value(OWN)=QLDCAdvanced: / Preserve Feature Order: Per Output Port
Tester
    BOOL_OP = OR
    TEST_CLAUSE = TEST @Value(OWN) = QLDC
    TEST_MODE = TEST
    PASSED -> Tester_2
Note: Tester_2 [Tester] / Test Clauses: LogicLeft ValueOperatorRight Value@Value(SERVSTAT)!=ABANDONOR@Value(SERVSTAT)!=INACTIVEAdvanced: / Preserve Feature Order: Per Output Port
Tester_2
    BOOL_OP = OR
    TEST_CLAUSE:
      TEST @Value(SERVSTAT) != ABANDON
      TEST @Value(SERVSTAT) != INACTIVE
    TEST_MODE = TEST
    PASSED -> StatisticsCalculator
StatisticsCalculator
    CALCULATION_MODE = NUMERIC
    FEAT_STATS = PIPELEN,NUMERIC_MODE,,,,SUM,,,,,,,,,
    GROUP_BY = system origin_utc OWN
    SUMMARY -> Junction_5
Junction_5
    -> Junction_6

Bookmark: load: to excel
Junction_6
    -> AttributeManager
Note: AttributeManager [AttributeManager] / Attribute Actions: Input AttributeOutput AttributeValueTypeActionOWNownervarchar(254)Renamedatapipe length in kmsbufferSet ValuePIPELEN.sumvalue@int(@Value(value)/1000)real64Rename
AttributeManager
    ATTR_TABLE:
      RENAME_SET_VALUE OWN > owner (varchar(254))
      SET_TO data (buffer) = pipe length in kms
      RENAME_SET_VALUE PIPELEN.sum > value (real64) = @int(@Value(value)/1000)
    -> export (writer CSV2_1)
export (writer CSV2_1)
    attributes: owner string, system string, data string, value real64, origin_utc datetime
