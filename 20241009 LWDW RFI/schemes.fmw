FME workspace schemes.fmw

Parameters:
- DestDataset_XLSXW_3 = $(FME_MF_DIR)outputs.xlsx   # Destination Microsoft Excel File

Writers:
- XLSXW_2: XLSXW to $(DestDataset_XLSXW_3)

Bookmark: datetime
Creator
    GEOMTYPE = Geometry Object
    NUM = 1
    CREATED -> origin_utc
origin_utc: DateTimeStamper
    DATETIME_ATTR = origin_utc
    INCLUDE_FRAC_SECONDS = NO
    INCLUDE_OFFSET = NO
    STAMP_TYPE = datetime
    TIMEZONE = utc
    -> Junction
Junction
    -> Junction_2

Bookmark: extract: scheme boundaries
Junction_2
    -> FeatureReader [INITIATOR]
FeatureReader
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Merge Initiator and Result
    ATTR_CONFLICT_RES = Use Result
    ATTR_IGNORE_NULLS = No
    COMBINE_GEOM = Use Result
    FORMAT = ARCGISONLINEFEATURES
    INTERACT = NONE
    ORDER_RESULTS = No
    OUTPUT_FEATURES_DISPLAY = Schema and Data Features
    Scheme Boundaries -> Junction_9
Junction_9
    -> Junction_10

Bookmark: exytract: scheme areas
Junction_10
    -> AttributeValueMapper
AttributeValueMapper
    LUT = 1,WS,2,WW,3,SW
    MAPPING_DIRECTION = FORWARD
    SRC = WaterType
    VAL_ATTR = system
    -> StatisticsCalculator_2
StatisticsCalculator_2
    CALCULATION_MODE = NUMERIC
    FEAT_STATS = Shape__Area,NUMERIC_MODE,,,,SUM,,,,,,,,,
    GROUP_BY = system origin_utc
    SUMMARY -> Junction_11
Junction_11
    -> Junction_12

Bookmark: load: to excel
Junction_12
    -> AttributeManager_2
AttributeManager_2
    ATTR_TABLE = RENAME_SET_VALUE Shape__Area.sum > area_km2 (real64) = @round(@Value(area_km2)/1000000,1)
    -> schemes (writer XLSXW_2)
schemes (writer XLSXW_2)
    attributes: system string(10), area_km2 number(10), origin_utc datetime(10)
