FME workspace connections-tech1.fmw

Bookmark: datetime
Creator
    GEOMTYPE = Geometry Object
    NUM = 1
    CREATED -> DateTimeStamper
DateTimeStamper
    DATETIME_ATTR = origin_utc
    INCLUDE_FRAC_SECONDS = YES
    INCLUDE_OFFSET = NO
    STAMP_TYPE = datetime
    TIMEZONE = utc
    -> Junction
Junction
    -> Junction_2

Bookmark: extract: water connections excel files from T1
Junction_2
    -> FeatureReader [INITIATOR]
    -> FeatureReader_2 [INITIATOR]
    -> FeatureReader_3 [INITIATOR]
FeatureReader
    ATTRIBUTES = StormWater-Level3-Report,"ParentAssessment,SWRatesQUAL,GRRatesQual,StormConns,StormSUIPs,StormDemUnits,fme_basename"
    ATTR_ACCUM_MODE = Merge Initiator and Result
    ATTR_CONFLICT_RES = Use Result
    ATTR_IGNORE_NULLS = No
    COMBINE_GEOM = Use Result
    DATASET = $(FME_MF_DIR_ENCODED)Tech1\StormWater-Level3-Report.xls.xlsx
    FORMAT = XLSXR
    INTERACT = NONE
    ORDER_RESULTS = No
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = $(FME_MF_DIR)Tech1\StormWater-Level3-Report.xls.xlsx
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = StormWater-Level3-Report,0,ParentAssessment,number,10,0,,1,SWRatesQUAL,char,37,,,2,GRRatesQual,char,32,,,3,StormConns,number,1,0,,4,StormSUIPs,number,2,0,,5,StormDemUnits,number,1,0,,1,,,,NO,NO,1,C:\Github\qldc-pi-fme-taumata-dev\Tech1\StormWater-Level3-Report.xls.xlsx,"0,0,5,21069",,NO,NO
    XLSXR_SCHEMA_HANDLING_REVISION = 2
    XLSXR_SKIP_EMPTY_ROWS = YES
    XLSXR_STRIP_SHEETNAME_SPACES = YES
    XLSXR_TABLELIST = StormWater-Level3-Report
    XLSXR_TRIM_ATTR_NAME_WHITESPACE = Yes
    XLSXR_USE_CUSTOM_SCHEMA = NO
    XLSXR_XLSXR_EXPOSE_FORMAT_ATTRS = fme_basename,char(50)
    StormWater-Level3-Report -> AttributeRenamer
    StormWater-Level3-Report -> Junction_15
AttributeRenamer
    ATTR_TABLE:
      RENAME_SET_DEFAULT StormConns > Conns
      RENAME_SET_DEFAULT StormDemUnits > DemUnits
      RENAME_SET_DEFAULT StormSUIPs > Suips
      RENAME_SET_DEFAULT SWRatesQUAL > RatesQUAL
    MISSING_INPUT_ATTRS = REMOVE
    -> Junction_3
Junction_3
    -> Junction_4
Junction_15
    -> Junction_16
FeatureReader_2
    ATTRIBUTES = WasteWater-Level3-Report,"ParentAssessment,WWRatesQual,GRRatesQual,AssNumSewerConns,AssNumSewerPans,AssNumSewerDem,fme_basename"
    ATTR_ACCUM_MODE = Merge Initiator and Result
    ATTR_CONFLICT_RES = Use Result
    ATTR_IGNORE_NULLS = No
    COMBINE_GEOM = Use Result
    DATASET = $(FME_MF_DIR_ENCODED)Tech1\WasteWater-Level3-Report.xls.xlsx
    FORMAT = XLSXR
    INTERACT = NONE
    ORDER_RESULTS = No
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = $(FME_MF_DIR)Tech1\WasteWater-Level3-Report.xls.xlsx
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = WasteWater-Level3-Report,0,ParentAssessment,number,10,0,,1,WWRatesQual,char,24,,,2,GRRatesQual,char,39,,,3,AssNumSewerConns,number,2,0,,4,AssNumSewerPans,number,2,0,,5,AssNumSewerDem,number,2,0,,1,,,,NO,NO,1,C:\Github\qldc-pi-fme-taumata-dev\Tech1\WasteWater-Level3-Report.xls.xlsx,"0,0,5,17114",,NO,NO
    XLSXR_SCHEMA_HANDLING_REVISION = 2
    XLSXR_SKIP_EMPTY_ROWS = YES
    XLSXR_STRIP_SHEETNAME_SPACES = YES
    XLSXR_TABLELIST = WasteWater-Level3-Report
    XLSXR_TRIM_ATTR_NAME_WHITESPACE = Yes
    XLSXR_USE_CUSTOM_SCHEMA = NO
    XLSXR_XLSXR_EXPOSE_FORMAT_ATTRS = fme_basename,char(50)
    WasteWater-Level3-Report -> AttributeRenamer_2
    WasteWater-Level3-Report -> Junction_11
AttributeRenamer_2
    ATTR_TABLE:
      RENAME_SET_DEFAULT AssNumSewerConns > Conns
      RENAME_SET_DEFAULT AssNumSewerDem > DemUnits
      RENAME_SET_DEFAULT AssNumSewerPans > Suips
      RENAME_SET_DEFAULT WWRatesQual > RatesQUAL
    MISSING_INPUT_ATTRS = REMOVE
    -> Junction_5
Junction_5
    -> Junction_6
Junction_11
    -> Junction_12
FeatureReader_3
    ATTRIBUTES = Water-Level3-Report,"ParentAssessment,WSRatesQUAL,WSRatesQualLU,GRRatesQual,WaterConns,WaterSUIPs,WaterDemUnits,fme_basename"
    ATTR_ACCUM_MODE = Merge Initiator and Result
    ATTR_CONFLICT_RES = Use Result
    ATTR_IGNORE_NULLS = No
    COMBINE_GEOM = Use Result
    DATASET = $(FME_MF_DIR_ENCODED)Tech1\Water-Level3-Report.xls.xlsx
    FORMAT = XLSXR
    INTERACT = NONE
    ORDER_RESULTS = No
    OUTPUT_FEATURES_DISPLAY = Schema and Data Features
    XLSXR_ALLOW_DOLLAR_SIGNS = YES
    XLSXR_APPLY_FILTERS = No
    XLSXR_CASE_SENSITIVE_FEATURE_TYPES = YES
    XLSXR_CONFIGURATION_DATASET = $(FME_MF_DIR)Tech1\Water-Level3-Report.xls.xlsx
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = Water-Level3-Report,0,ParentAssessment,date,,,,1,WSRatesQUAL,char,32,,,2,WSRatesQualLU,char,44,,,3,GRRatesQual,char,39,,,4,WaterConns,number,1,0,,5,WaterSUIPs,number,2,0,,6,WaterDemUnits,number,2,0,,1,,,,NO,NO,1,C:\Github\qldc-pi-fme-taumata-dev\Tech1\Water-Level3-Report.xls.xlsx,"0,0,6,20766",,NO,NO
    XLSXR_SCHEMA_HANDLING_REVISION = 2
    XLSXR_SKIP_EMPTY_ROWS = YES
    XLSXR_STRIP_SHEETNAME_SPACES = YES
    XLSXR_TABLELIST = Water-Level3-Report
    XLSXR_TRIM_ATTR_NAME_WHITESPACE = Yes
    XLSXR_USE_CUSTOM_SCHEMA = NO
    XLSXR_XLSXR_EXPOSE_FORMAT_ATTRS = fme_basename,char(50)
    Water-Level3-Report -> AttributeRenamer_3
    Water-Level3-Report -> Junction_13
AttributeRenamer_3
    ATTR_TABLE:
      RENAME_SET_DEFAULT WaterConns > Conns
      RENAME_SET_DEFAULT WaterDemUnits > DemUnits
      RENAME_SET_DEFAULT WaterSUIPs > Suips
      RENAME_SET_DEFAULT WSRatesQUAL > RatesQUAL
    MISSING_INPUT_ATTRS = REMOVE
    -> Junction_7
Junction_7
    -> Junction_8
Junction_13
    -> Junction_14

Bookmark: transform: merge and analyse
Junction_4
    -> AttributeManager
Junction_6
    -> AttributeManager
Junction_8
    -> AttributeManager
AttributeManager
    ATTR_TABLE = REMOVE WSRatesQualLU (varchar(44))
    -> AttributeValueMapper
Note: AttributeValueMapper [AttributeValueMapper] / Attribute Selection: / Input Attribute: fme_basename / Output Attribute: system / Value Map: / Default Output Value: <not set> / Mapping Direction: Forward (Input To Output) Input ValueOutput ValueWater-Level3-Report.xlsWater SupplyStormWater-Level3-Report.xlsStormwaterWasteWater-Level3-Report.xlsWastewater
AttributeValueMapper
    LUT = Water-Level3-Report.xls,Water Supply,StormWater-Level3-Report.xls,Stormwater,WasteWater-Level3-Report.xls,Wastewater
    MAPPING_DIRECTION = FORWARD
    SRC = fme_basename
    VAL_ATTR = system
    -> AttributeValueMapper_2
Note: AttributeValueMapper_2 [AttributeValueMapper] / Attribute Selection: / Input Attribute: GRRatesQual / Output Attribute: use / Value Map: / Default Output Value: Other / Mapping Direction: Forward (Input To Output) Input ValueOutput ValueGeneral Rate ResidentialResidentialGeneral Rate - Vacant SectionsVacantGeneral Rate - Mixed Use AccomResidentialGeneral Rate Residence plus FlatResidentialGeneral Rate CommercialNon-ResidentialGeneral Rate - Country DwgNon-ResidentialGeneral Rate - AccommodationResidentialGeneral Rate - CBD CommercialNon-ResidentialGeneral Rate - Mixed Use Accom/Res FlatResidentialGeneral Rate - Primary Ind.Non-ResidentialGeneral Rate - Mixed Use Comm.Non-ResidentialGeneral Rate - M/Use Accom/CDwResidentialGeneral Rate - Ctry Dwg plus FlatNon-ResidentialGeneral Rate - CBD Accomm.ResidentialGeneral Rate - OtherNon-ResidentialGeneral Rate - M/Use Acc/CDwg FlatResidentialGeneral Rate - M/Use Com C/DwgNon-ResidentialGeneral Rate 50%Non-ResidentialGeneral Rate 50% CommercialNon-ResidentialGeneral Rate - Hydro/UtilityNon-Residential1 more row(s)...
AttributeValueMapper_2
    DEFAULT_VALUE = Other
    LUT = General Rate Residential,Residential,General Rate - Vacant Sections,Vacant,General Rate - Mixed Use Accom,Residential,General Rate Residence plus Flat,Residential,General Rate Commercial,Non-Residential,General Rate - Country Dwg,Non-Residential,General Rate - Accommodation,Residential,General Rate - CBD Commercial,Non-Residential,General Rate - Mixed Use Accom/Res Flat,Residential,General Rate - Primary Ind.,Non-Residential,General Rate - Mixed Use Comm.,Non-Residential,General Rate - M/Use Accom/CDw,Residential,General Rate - Ctry Dwg plus Flat,Non-Residential,General Rate - CBD Accomm.,Residential,General Rate - Other,Non-Residential,General Rate - M/Use Acc/CDwg Flat,Residential,General Rate - M/Use Com C/Dwg,Non-Residential,General Rate 50%,Non-Residential,General Rate 50% Commercial,Non-Residential,General Rate - Hydro/Utility,Non-Residential,General Rate - M/Use Com. 10%,Non-Residential
    MAPPING_DIRECTION = FORWARD
    SRC = GRRatesQual
    VAL_ATTR = use
    -> Junction_9
Junction_9
    -> Junction_10

Bookmark: load: total number of demand units
Junction_16
    -> sw_demand
sw_demand: StatisticsCalculator
    CALCULATION_MODE = NUMERIC
    FEAT_STATS = StormDemUnits,NUMERIC_MODE,,,,SUM,,,,,,,,,
Junction_12
    -> ww_demand
ww_demand: StatisticsCalculator
    CALCULATION_MODE = NUMERIC
    FEAT_STATS = AssNumSewerDem,NUMERIC_MODE,,,,SUM,,,,,,,,,
Junction_14
    -> ws_demand
ws_demand: StatisticsCalculator
    CALCULATION_MODE = NUMERIC
    FEAT_STATS = WaterDemUnits,NUMERIC_MODE,,,,SUM,,,,,,,,,

Bookmark: transform: statistics
Junction_10
    -> Tester
Tester
    BOOL_OP = AND
    TEST_CLAUSE:
      TEST @Value(use) != Vacant
      TEST @Value(use) != Other
    TEST_MODE = TEST
    PASSED -> StatisticsCalculator
StatisticsCalculator
    CALCULATION_MODE = NUMERIC
    FEAT_STATS = Conns,NUMERIC_MODE,,,,SUM,,,,,,,,,
    GROUP_BY = system use
    SUMMARY -> Sorter
Sorter
    SORT_PARM = system NATURAL ASCENDING use NATURAL ASCENDING
