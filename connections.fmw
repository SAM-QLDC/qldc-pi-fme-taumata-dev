FME workspace connections.fmw

Bookmark: extract: old rates DB
Creator
    GEOMTYPE = Geometry Object
    NUM = 1
    CREATED -> FeatureReader [INITIATOR]
    CREATED -> FeatureReader_2 [INITIATOR]
FeatureReader
    ATTRIBUTES = "WS Connections May 2023","ParentAssN,SUM_LAND_V,SUM_CAPITA,SUM_IMPROV,Shape_Leng,Shape_Area,ParentAsse,WSRatesQUA,WSRatesQ_1,GRRatesQua,WaterConns,WaterSUIPs,WaterDemUn,ObjectID"
    ATTR_ACCUM_MODE = Only Use Result
    COMBINE_GEOM = Use Result
    DATASET = $(FME_MF_DIR_ENCODED)gis\WS Connections May 2023.zip
    FORMAT = SHAPEFILE
    INTERACT = NONE
    ORDER_RESULTS = No
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    WS Connections May 2023 -> Junction
    WS Connections May 2023 -> Junction_3
Junction
    -> Junction_2
Junction_3
    -> Junction_5
FeatureReader_2
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Only Use Result
    COMBINE_GEOM = Use Result
    FORMAT = ARCGISONLINEFEATURES
    INTERACT = NONE
    ORDER_RESULTS = No
    OUTPUT_FEATURES_DISPLAY = Schema and Data Features
    Scheme Boundaries -> Junction_4
Junction_4
    -> Junction_6

Bookmark: edm: check on fields to understand what its telling me!
Junction_2 [off]
    -> WSRatesQUA
    -> WSRatesQ_1
    -> GRRatesQua
Note: possible how each parcel gets charged for their water
WSRatesQUA: UniqueValueLogger
    VAL = @Value(WSRatesQUA)
Note: main planning type of zones
WSRatesQ_1: UniqueValueLogger
    VAL = @Value(WSRatesQ_1)
Note: seems good to split up into uses for each parcel
GRRatesQua: UniqueValueLogger
    VAL = @Value(GRRatesQua)

Bookmark: transform: within scheme areas
Junction_5
    -> AttributeValueMapper
AttributeValueMapper
    DEFAULT_VALUE = other
    LUT = General Rate Residential,residential,General Rate - Vacant Sections,vacant,General Rate - Mixed Use Accom,non-residential,General Rate Residence plus Flat,residential,General Rate Commercial,non-residential,General Rate - Country Dwg,non-residential,General Rate - Accommodation,residential,General Rate - CBD Commercial,non-residential,General Rate - Mixed Use Accom/Res Flat,residential,General Rate - Primary Ind.,non-residential,General Rate - Mixed Use Comm.,non-residential,General Rate - M/Use Accom/CDw,residential,General Rate - Ctry Dwg plus Flat,non-residential,General Rate - CBD Accomm.,residential,General Rate - Other,non-residential,General Rate - M/Use Acc/CDwg Flat,residential,General Rate - M/Use Com C/Dwg,non-residential,General Rate 50%,non-residential,General Rate 50% Commercial,non-residential,General Rate - Hydro/Utility,other,General Rate - M/Use Com. 10%,non-residential
    MAPPING_DIRECTION = FORWARD
    SRC = GRRatesQua
    VAL_ATTR = use
    -> CenterPointReplacer
    -> Junction_9
CenterPointReplacer
    POINTTYPE = CENTER
    POINT -> Tester
Note: Tester [Tester] / Test Clauses: Left ValueOperatorRight Value@Value(use)!=residentialAdvanced: / Preserve Feature Order: Per Output Port
Tester
    BOOL_OP = OR
    TEST_CLAUSE = TEST @Value(use) != residential
    TEST_MODE = TEST
    PASSED -> AttributeKeeper_2
AttributeKeeper_2
    CREATE_BULK_MODE_FEATURES = NO
    KEEP_ATTRS = WaterConns
    -> PointOnAreaOverlayer [POINT]
Junction_9
    -> Junction_10
Junction_6
    -> AttributeValueMapper_2
AttributeValueMapper_2
    LUT = 1,Water Supply,2,Wastewater,3,Stormwater
    MAPPING_DIRECTION = FORWARD
    SRC = WaterType
    VAL_ATTR = use
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(WaterType) = 1",water supply,"BOOL_OP,OR,COMPOSITE_TEST,""""""1"""""",TEST_CLAUSE,TEST @Value(WaterType) = 2",wastewater,"BOOL_OP,OR,COMPOSITE_TEST,""""""1"""""",TEST_CLAUSE,TEST @Value(WaterType) = 3",stormwater
    water supply -> AttributeKeeper
AttributeKeeper
    CREATE_BULK_MODE_FEATURES = NO
    KEEP_ATTRS = WaterType
    -> PointOnAreaOverlayer [AREA]
PointOnAreaOverlayer
    ATTR_ACCUM_MODE = Prefic Incoming
    DEAGGREGATE_INPUT = Yes
    INCOMING_PREFIX = _
    OV_ATTR = _overlaps
    POLYS_FIRST = NO
    POINT -> Junction_7
Junction_7
    -> Junction_8

Bookmark: New Bookmark
Junction_10
    -> StatisticsCalculator
StatisticsCalculator
    CALCULATION_MODE = NUMERIC
    FEAT_STATS = WaterConns,NUMERIC_MODE,,,,SUM,,,,,,,,,
    GROUP_BY = use
Junction_8
    -> AttributeCreator
AttributeCreator
    ATTR_TABLE = SET_TO extent (varchar(200)) = FME_CONDITIONAL:DEFAULT_VALUE'in'BOOL_OP;OR;COMPOSITE_TEST;1;TEST _WaterType ATTRIBUTE_IS_MISSING _FME_BLANK_STRING_'out'FME_NUM_CONDITIONS2___
    -> StatisticsCalculator_2
StatisticsCalculator_2
    CALCULATION_MODE = NUMERIC
    FEAT_STATS = WaterConns,NUMERIC_MODE,,,,SUM,,,,,,,,,
    GROUP_BY = extent

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
