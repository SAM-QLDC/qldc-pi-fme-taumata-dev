FME workspace network.fmw

Parameters:
- DestDataset_CSV2 = C:\Github\qldc-pi-fme-taumata-dev   # Destination CSV (Comma Separated Value) Folder

Writers:
- CSV2_1: CSV2 to $(DestDataset_CSV2)

Note: may need to filter for FY - 30th June 2024??
Note: change the source data set to the SDE tables instead of the public AGOL files
Note: next improvement is to do a weigyted average

Bookmark: datetime
Creator
    GEOMTYPE = Geometry Object
    NUM = 1
    CREATED -> origin_utc
origin_utc: DateTimeStamper
    DATETIME_ATTR = origin_utc
    INCLUDE_FRAC_SECONDS = NO
    INCLUDE_OFFSET = NO
    STAMP_TYPE = datetime
    TIMEZONE = utc
    -> Junction_7
Junction_7
    -> Junction_8

Bookmark: extract: 3 water pipes
Junction_8
    -> _Three_Waters_Assets [INITIATOR]
_Three_Waters_Assets: FeatureReader
    ARCGISONLINEFEATURES_CREATE_FEATURE_TABLES_FROM_DATA = Yes
    ARCGISONLINEFEATURES_FEATURESERVICE = Queenstown Lakes District Council Open Data/Three Waters Assets(a99d1860d32f44fbb025142a364d0458)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Stormwater Channel","OBJECTID,COMPKEY,ASSETTYPE,DESCR,SERVSTAT,OWN,CONMATL,LENGTH,TPWIDTH,BSWIDTH,CHDEPTH,CHANSHAPE,UPNODE,UPSELEV,DWNNODE,DWNELEV,INSTDATE,ASBUILT,SCHEME,DATA_SRC,COMMENTS,ADDDBY,ADDDTTM,MODBY,MODDTTM,CONFIDENCE,CRITICALITY,GlobalID,created_user,created_date,last_edited_user,last_edited_date,Shape__Length","Stormwater Inlet","OBJECTID,COMPKEY,ASSETTYPE,DESCR,SERVSTAT,OWN,ZCOORD,INVERTELEV,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Lateral","OBJECTID,COMPKEY,ASSETTYPE,SRVTYPE,DESCR,SERVSTAT,OWN,PIPEMATL,PIPELEN,NOMDIAM,INTDIAM,OUTDIAM,UPNODE,UPSELEV,DWNNODE,DWNELEV,CLASS,JTTYPE,MANUFCT,INSTDATE,ASBUILT,SCHEME,DATA_SRC,COMMENTS,ADDDBY,ADDDTTM,MODBY,MODDTTM,CONFIDENCE,CRITICALITY,GlobalID,created_user,created_date,last_edited_user,last_edited_date,Shape__Length","Stormwater Main","OBJECTID,COMPKEY,ASSETTYPE,DESCR,SERVSTAT,OWN,PIPEMATL,PIPELEN,NOMDIAM,INTDIAM,OUTDIAM,UPNODE,UPSELEV,DWNNODE,DWNELEV,CLASS,JTTYPE,MANUFCT,INSTMTHD,INSTDATE,LINEMATL,LINEDATE,LINEMTHD,ASBUILT,SCHEME,DATA_SRC,COMMENTS,ADDDBY,ADDDTTM,MODBY,MODDTTM,CONFIDENCE,CRITICALITY,GlobalID,created_user,created_date,last_edited_user,last_edited_date,Shape__Length","Stormwater Manhole","OBJECTID,COMPKEY,ASSETTYPE,DESCR,SERVSTAT,OWN,ZCOORD,INVERTELEV,BARLSHAPE,BARLDIAM,BARLDIM2,CHAMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date","Stormwater Meter","OBJECTID,COMPKEY,ASSETTYPE,DESCR,SERVSTAT,OWN,ZCOORD,INVERTELEV,METERSZ,SERNO,MODELNO,INSTDATE,ASBUILT,SCHEME,DATA_SRC,COMMENTS,ADDDBY,ADDDTTM,MODBY,MODDTTM,CONFIDENCE,CRITICALITY,GlobalID,created_user,created_date,last_edited_user,last_edited_date","Stormwater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Stormwater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Stormwater Structure","OBJECTID,COMPKEY,ASSETTYPE,DESCR,SERVSTAT,OWN,ZCOORD,MANUFCT,INSTDATE,ASBUILT,SCHEME,DATA_SRC,COMMENTS,ADDDBY,ADDDTTM,MODBY,MODDTTM,CONFIDENCE,CRITICALITY,GlobalID,created_user,created_date,last_edited_user,last_edited_date","Stormwater Treatment Device","OBJECTID,COMPKEY,ASSETTYPE,DESCR,SERVSTAT,OWN,ZCOORD,INVERTELEV,DEVCAREA,BARLDIAM,BARLDIM2,DVCMATL,CVRDIAM,CVRTYPE,MANUFCT,INSTDATE,ASBUILT,SCHEME,DATA_SRC,COMMENTS,ADDDBY,ADDDTTM,MODBY,MODDTTM,CONFIDENCE,CRITICALITY,GlobalID,created_user,created_date,last_edited_user,last_edited_date,VOIDMAT","Stormwater Treatment Device Area","OBJECTID,COMPKEYREF,COMMENTS,ADDDBY,ADDDTTM,MODBY,MODDTTM,GlobalID,created_user,created_date,last_edited_user,last_edited_date,Shape__Area,Shape__Length","Stormwater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Wastewater Main","OBJECTID,COMPKEY,ASSETTYPE,DESCR,SERVSTAT,OWN,PIPEMATL,PIPELEN,NOMDIAM,INTDIAM,OUTDIAM,UPNODE,UPSELEV,DWNNODE,DWNELEV,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Wastewater Manhole","OBJECTID,COMPKEY,ASSETTYPE,SUBTYPE,DESCR,SERVSTAT,OWN,ZCOORD,INVERTELEV,BARLSHAPE,BARLDIAM,BARLDIM2,CHAMATL,CVRTYPE,CVRDIAM,MANUFCT,INSTDATE,ASBUILT,SCHEME,DATA_SRC,COMMENTS,ADDDBY,ADDDTTM,MODBY,MODDTTM,CONFIDENCE,CRITICALITY,GlobalID,created_user,created_date,last_edited_user,last_edited_date","Wastewater Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Wastewater Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Wastewater Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Wastewater Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Backflow","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Hydrant","OBJECTID,COMPKEY,ASSETTYPE,DESCR,SERVSTAT,OWN,ZCOORD,INVERTELEV,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Lateral","OBJECTID,COMPKEY,ASSETTYPE,SRVTYPE,DESCR,SERVSTAT,OWN,PIPEMATL,PIPELEN,NOMDIAM,INTDIAM,OUTDIAM,CLASS,MANUFCT,INSTDATE,ASBUILT,SCHEME,DATA_SRC,COMMENTS,ADDDBY,ADDDTTM,MODBY,MODDTTM,CONFIDENCE,CRITICALITY,GlobalID,created_user,created_date,last_edited_user,last_edited_date,Shape__Length","Water Supply Main","OBJECTID,COMPKEY,ASSETTYPE,DESCR,SERVSTAT,OWN,PIPEMATL,PIPELEN,NOMDIAM,INTDIAM,OUTDIAM,DPTH,UPNODE,DWNNODE,CLASS,INSTDATE,JTTYPE,MANUFCT,INSTMTHD,LINEMATL,LINEMTHD,LINEDATE,ASBUILT,SCHEME,DATA_SRC,COMMENTS,ADDDBY,ADDDTTM,MODBY,MODDTTM,CONFIDENCE,CRITICALITY,GlobalID,created_user,created_date,last_edited_user,last_edited_date,Shape__Length","Water Supply Meter","OBJECTID,COMPKEY,ASSETTYPE,DESCR,SERVSTAT,OWN,ZCOORD,INVERTELEV,METERSZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date","Water Supply Miscellaneous","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,GlobalID,created_user,created_date,last_edited_user,last_edited_date,Shape__Area,Shape__Length","Water Supply Node","OBJECTID,COMPKEY,ASSETTYPE,DESCR,SERVSTAT,OWN,ZCOORD,INVERTELEV,INSTDATE,ASBUILT,SCHEME,DATA_SRC,COMMENTS,ADDDBY,ADDDTTM,MODBY,MODDTTM,CONFIDENCE,CRITICALITY,GlobalID,created_user,created_date,last_edited_user,last_edited_date","Water Supply Pressure Zones","OBJECTID,Id,Zone_Name,Name_Code,Rated_Cons,GlobalID,created_user,created_date,last_edited_user,last_edited_date,Shape__Area,Shape__Length","Water Supply Pumpstation","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Reservoir","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Treatment Plant","OBJECTID,COMPKEY,ASSETTYPE,DESCR,SERVSTAT,OWN,ZCOORD,INSTDATE,ASBUILT,SCHEME,DATA_SRC,COMMENTS,ADDDBY,ADDDTTM,MODBY,MODDTTM,CONFIDENCE,CRITICALITY,created_user,created_date,last_edited_user,last_edited_date,GlobalID,Shape__Area,Shape__Length","Water Supply Valve","OBJECTID,COMPKEY,ASSETTYPE,DESCR,SERVSTAT,OWN,ZCOORD,INVERTELEV,VALVESTAT,VALVESZ,SERNO,MODELNO,MANUFCT,INSTDATE,ASBUILT,SCHEME,DATA_SRC,COMMENTS,ADDDBY,ADDDTTM,MODBY,MODDTTM,CONFIDENCE,CRITICALITY,GlobalID,created_user,created_date,last_edited_user,last_edited_date"
    ATTR_ACCUM_MODE = Merge Initiator and Result
    ATTR_CONFLICT_RES = Use Result
    ATTR_IGNORE_NULLS = No
    COMBINE_GEOM = Use Result
    FEATURETYPES = Stormwater Lateral Stormwater Main Wastewater Lateral Wastewater Main Water Supply Lateral Water Supply Main
    FORMAT = ARCGISONLINEFEATURES
    INTERACT = NONE
    ORDER_RESULTS = No
    OUTPUT_FEATURES_DISPLAY = Schema and Data Features
    Stormwater Lateral -> AttributeCreator_3
    Stormwater Main -> AttributeCreator_6
    Wastewater Lateral -> AttributeCreator
    Wastewater Main -> AttributeCreator_2
    Water Supply Lateral -> AttributeCreator_4
    Water Supply Main -> AttributeCreator_5
AttributeCreator_3
    ATTR_TABLE = SET_TO system (buffer) = SW
    -> Junction
AttributeCreator
    ATTR_TABLE = SET_TO system (buffer) = WW
    -> Junction
AttributeCreator_4
    ATTR_TABLE = SET_TO system (buffer) = WS
    -> Junction
Junction
    -> Junction_2
AttributeCreator_6
    ATTR_TABLE = SET_TO system (buffer) = SW
    -> Junction_3
AttributeCreator_2
    ATTR_TABLE = SET_TO system (buffer) = WW
    -> Junction_3
AttributeCreator_5
    ATTR_TABLE = SET_TO system (buffer) = WS
    -> Junction_3
Junction_3
    -> Junction_4

Bookmark: transform: filter data
Junction_2
    -> AttributeKeeper
Junction_4
    -> AttributeCreator_8
Note: AttributeCreator_8 [AttributeCreator] / New Attributes: Output AttributeValueTypePIPELEN@double(@Value(PIPELEN)/1)real64OWNFME_CONDITIONAL:DEFAULT_VALUE'QLDC'BOOL_OP;OR;COMPOSITE_TEST;1;TEST OWN ATTRIBUTE_HAS_A_VALUE _FME_BLANK_STRING_'<at>Value<openparen>OWN<closeparen>'FME_NUM_CONDITIONS2___varchar(254)
AttributeCreator_8
    ATTR_TABLE:
      SET_TO PIPELEN (real64) = @double(@Value(PIPELEN)/1)
      SET_TO OWN (varchar(254)) = FME_CONDITIONAL:DEFAULT_VALUE'QLDC'BOOL_OP;OR;COMPOSITE_TEST;1;TEST OWN ATTRIBUTE_HAS_A_VALUE _FME_BLANK_STRING_'@Value(OWN)'FME_NUM_CONDITIONS2___
    -> AttributeKeeper
AttributeKeeper
    CREATE_BULK_MODE_FEATURES = NO
    KEEP_ATTRS = OBJECTID,ASSETTYPE,COMPKEY,PIPELEN,OWN,SERVSTAT,system,origin_utc,INSTDATE
    -> Tester
Note: Tester [Tester] / Test Clauses: Left ValueOperatorRight Value@Value(OWN)=QLDCAdvanced: / Preserve Feature Order: Per Output Port
Tester
    BOOL_OP = OR
    TEST_CLAUSE = TEST @Value(OWN) = QLDC
    TEST_MODE = TEST
    PASSED -> Tester_2
Note: Tester_2 [Tester] / Test Clauses: LogicLeft ValueOperatorRight Value@Value(SERVSTAT)!=ABANDONOR@Value(SERVSTAT)!=REMOVEDAdvanced: / Preserve Feature Order: Per Output Port
Tester_2
    BOOL_OP = OR
    TEST_CLAUSE:
      TEST @Value(SERVSTAT) != ABANDON
      TEST @Value(SERVSTAT) != REMOVED
    TEST_MODE = TEST
    PASSED -> Junction_9
Junction_9
    -> Junction_10

Bookmark: transform: network lengths
Junction_10
    -> StatisticsCalculator
    -> Junction_13
StatisticsCalculator
    CALCULATION_MODE = NUMERIC
    FEAT_STATS = PIPELEN,NUMERIC_MODE,,,,SUM,,,,,,,,,
    GROUP_BY = system origin_utc OWN
    SUMMARY -> AttributeManager
Note: AttributeManager [AttributeManager] / Attribute Actions: Input AttributeOutput AttributeValueTypeActionsourceGISbufferSet ValueOWNownervarchar(254)RenamedataLength of Reticulated Network (km)bufferSet ValuePIPELEN.sumvalue@int(@Value(value)/1000)real64Renamevalue_flag500uint64Set Valuedata_improvementwe have assumed 100pc of the length of laterals is in private ownership. Improvements can be made by hovering the toby over the lateral to get a better estimate of private public lengths for lateral p ... bufferSet Value
AttributeManager
    ATTR_TABLE:
      SET_TO source (buffer) = GIS
      RENAME_SET_VALUE OWN > owner (varchar(254))
      SET_TO data (buffer) = Length of Reticulated Network (km)
      RENAME_SET_VALUE PIPELEN.sum > value (real64) = @int(@Value(value)/1000)
      SET_TO value_flag (uint64) = 500
      SET_TO data_improvement (buffer) = we have assumed 100pc of the length of laterals is in private ownership. Improvements can be made by hovering the toby over the lateral to get a better estimate of private public lengths for lateral pipes
    -> Junction_5
Junction_5
    -> Junction_6
Junction_13
    -> Junction_14

Bookmark: load: 2csv
Junction_6
    -> Junction_15
Junction_12
    -> Junction_15
Junction_15
    -> export (writer CSV2_1)
export (writer CSV2_1) [off]
    attributes: source string, owner string, system string, data string, value real64, value_flag uint64, origin_utc datetime, data_improvement string

Bookmark: transform: average pipe age
Junction_14
    -> Tester_3
Tester_3
    BOOL_OP = OR
    TEST_CLAUSE = TEST INSTDATE ATTRIBUTE_HAS_A_VALUE ""
    TEST_MODE = TEST
    PASSED -> AttributeCreator_7
AttributeCreator_7
    ATTR_TABLE = SET_TO age (varchar(200)) = @int(@DateTimeFormat(@Value(origin_utc),%Y)-@DateTimeFormat(@Value(INSTDATE),%Y))
    -> StatisticsCalculator_2
StatisticsCalculator_2
    CALCULATION_MODE = NUMERIC
    FEAT_STATS = age,NUMERIC_MODE,,,,,MEAN,,,,,,,,
    GROUP_BY = system origin_utc OWN
    SUMMARY -> AttributeManager_2
Note: AttributeManager_2 [AttributeManager] / Attribute Actions: Input AttributeOutput AttributeValueTypeActionsourceGISbufferSet ValueOWNownervarchar(254)RenamedataAverage Age of Reticulated Network (years)bufferSet Valueage.meanvalue@round(@Value(value),1)real64Renamevalue_flag500uint64Set Valuedata_improvementredraw and expand scheme areas currently the dataset is two years oldbufferSet Value
AttributeManager_2
    ATTR_TABLE:
      SET_TO source (buffer) = GIS
      RENAME_SET_VALUE OWN > owner (varchar(254))
      SET_TO data (buffer) = Average Age of Reticulated Network (years)
      RENAME_SET_VALUE age.mean > value (real64) = @round(@Value(value),1)
      SET_TO value_flag (uint64) = 500
      SET_TO data_improvement (buffer) = redraw and expand scheme areas currently the dataset is two years old
    -> Junction_11
Junction_11
    -> Junction_12
