FME workspace schemes.fmw

Parameters:
- DestDataset_CSV2 = C:\Github\qldc-pi-fme-taumata-dev   # Destination CSV (Comma Separated Value) Folder

Writers:
- CSV2_1: CSV2 to $(DestDataset_CSV2)

Bookmark: datetime
Creator
    GEOMTYPE = Geometry Object
    NUM = 1
    CREATED -> origin_utc
origin_utc: DateTimeStamper
    DATETIME_ATTR = origin_utc
    INCLUDE_FRAC_SECONDS = NO
    INCLUDE_OFFSET = NO
    STAMP_TYPE = datetime
    TIMEZONE = utc
    -> Junction
Junction
    -> Junction_2

Bookmark: extract: scheme boundaries
Junction_2
    -> FeatureReader [INITIATOR]
FeatureReader
    ARCGISONLINEFEATURES_CREATE_FEATURE_TABLES_FROM_DATA = Yes
    ARCGISONLINEFEATURES_FEATURESERVICE = Queenstown Lakes District Council Open Data/Three Waters Schemes(c2b563e7c41f44a6ad5d04efd337d118)
    ARCGISONLINEFEATURES_FEATURES_PER_REQUEST = 1000
    ARCGISONLINEFEATURES_FORMAT_GUID = YES
    ARCGISONLINEFEATURES_NC = hywell Esri ArcGIS Online
    ARCGISONLINEFEATURES_QUERY_FEATURE_TYPES_FOR_MERGE_FILTERS = Yes
    ARCGISONLINEFEATURES_RESOLVE_DOMAINS = No
    ARCGISONLINEFEATURES_TABLELIST = "Scheme Boundaries"
    ARCGISONLINEFEATURES_USE_SEARCH_ENVELOPE = NO
    ATTRIBUTES = "Scheme Boundaries","OBJECTID,WaterType,Name,Ownership,Delivery,Maintenance,DecisionDate,VolumeRestrictions,Notes,GlobalID,created_user,created_date,last_edited_user,last_edited_date,Shape__Area,Shape__Length"
    ATTR_ACCUM_MODE = Merge Initiator and Result
    ATTR_CONFLICT_RES = Use Result
    ATTR_IGNORE_NULLS = No
    COMBINE_GEOM = Use Result
    FORMAT = ARCGISONLINEFEATURES
    INTERACT = NONE
    ORDER_RESULTS = No
    OUTPUT_FEATURES_DISPLAY = Schema and Data Features
    Scheme Boundaries -> Junction_9
Junction_9
    -> Junction_10

Bookmark: extract: scheme areas
Junction_10
    -> AttributeValueMapper
AttributeValueMapper
    LUT = 1,WS,2,WW,3,SW
    MAPPING_DIRECTION = FORWARD
    SRC = WaterType
    VAL_ATTR = system
    -> StatisticsCalculator_2
StatisticsCalculator_2
    CALCULATION_MODE = NUMERIC
    FEAT_STATS = Shape__Area,NUMERIC_MODE,,,,SUM,,,,,,,,,
    GROUP_BY = system origin_utc
    SUMMARY -> AttributeManager_2
Note: AttributeManager_2 [AttributeManager] / Attribute Actions: Input AttributeOutput AttributeValueTypeActionsourceGISbufferSet ValueownerQLDCbufferSet Valuedataterritorial area in km2bufferSet ValueShape__Area.sumvalue@round(@Value(value)/1000000,3)real64Renamedata_flag500uint64Set Valuedata improvementthe scheme layer is about two years old and needs updarting to include recent geenfield sitesbufferSet Value
AttributeManager_2
    ATTR_TABLE:
      SET_TO source (buffer) = GIS
      SET_TO owner (buffer) = QLDC
      SET_TO data (buffer) = territorial area in km2
      RENAME_SET_VALUE Shape__Area.sum > value (real64) = @round(@Value(value)/1000000,3)
      SET_TO data_flag (uint64) = 500
      SET_TO data improvement (buffer) = the scheme layer is about two years old and needs updarting to include recent geenfield sites
    -> Junction_3
Junction_3
    -> Junction_4

Bookmark: load: to excel
Junction_4
    -> export (writer CSV2_1)
export (writer CSV2_1)
    attributes: source string, owner string, system string, data string, value real64, data_flag uint64, origin_utc datetime, data improvement string
