FME workspace laterals.fmw

Readers:
- GEODATABASE_SDE_1: GEODATABASE_SDE

LineOnAreaOverlayer
    ATTR_ACCUM_MODE = Merge Incoming
    ATTR_CONFLICT_RES = Use Original
    CLEANING_TOLERANCE = Automatic
    DEAGGREGATE_INPUT = Yes
    OVERLAY_TYPE = LINE_ON_AREA
    OV_ATTR = _overlaps
    <REJECTED> -> LineOnAreaOverlayer__Rejected_
LineOnAreaOverlayer__Rejected_: Logger
    LOG_FEATURE = LOG_ONLY
    MAXCOORDS = 20
    MAXFEATS = 20
    MESSAGE = Feature is:
    SEVERITY = INFO

Bookmark: extract: parcels
Creator
    GEOMTYPE = Geometry Object
    NUM = 1
    CREATED -> FeatureReader [INITIATOR]
FeatureReader
    ATTRIBUTES = "WS Connections May 2023","ParentAssN,SUM_LAND_V,SUM_CAPITA,SUM_IMPROV,Shape_Leng,Shape_Area,ParentAsse,WSRatesQUA,WSRatesQ_1,GRRatesQua,WaterConns,WaterSUIPs,WaterDemUn,ObjectID"
    ATTR_ACCUM_MODE = Only Use Result
    COMBINE_GEOM = Use Result
    DATASET = $(FME_MF_DIR_ENCODED)gis\WS Connections May 2023.zip
    FORMAT = SHAPEFILE
    INTERACT = NONE
    ORDER_RESULTS = No
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    WS Connections May 2023 -> AttributeValueMapper
AttributeValueMapper
    DEFAULT_VALUE = Other
    LUT = General Rate Residential,Residential,General Rate - Vacant Sections,Vacant,General Rate - Mixed Use Accom,Mixed,General Rate Residence plus Flat,Residential,General Rate Commercial,Commercial,General Rate - Country Dwg,Other,General Rate - Accommodation,Accomodation,General Rate - CBD Commercial,Commercial,General Rate - Mixed Use Accom/Res Flat,Accomodation,General Rate - Primary Ind.,Industrial,General Rate - Mixed Use Comm.,Commercial,General Rate - M/Use Accom/CDw,Residential,General Rate - Ctry Dwg plus Flat,Other,General Rate - CBD Accomm.,Accomodation,General Rate - Other,Other,General Rate - M/Use Acc/CDwg Flat,Accomodation,General Rate - M/Use Com C/Dwg,Commercial,General Rate 50%,Commercial,General Rate 50% Commercial,Commercial,General Rate - Hydro/Utility,Utility,General Rate - M/Use Com. 10%,Commercial
    MAPPING_DIRECTION = FORWARD
    SRC = GRRatesQua
    VAL_ATTR = use
    -> Junction
Junction
    -> Junction_2

Bookmark: transform: identify resiidential laterals
Junction_2
    -> Tester
Tester
    BOOL_OP = OR
    TEST_CLAUSE = TEST @Value(use) = Residential
    TEST_MODE = TEST
    PASSED -> LineOnAreaOverlayer [AREA]

Bookmark: extract: laterals
swLateral (reader GEODATABASE_SDE_1) [off]
    attributes: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
wsLateral (reader GEODATABASE_SDE_1) [off]
    attributes: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
wwLateral (reader GEODATABASE_SDE_1)
    attributes: OBJECTID integer, COMPKEY integer, ASSETTYPE char(254), SRVTYPE char(254), DESCR char(254), SERVSTAT char(254), OWN char(254), PIPEMATL char(254), PIPELEN double, NOMDIAM double, INTDIAM double, OUTDIAM double, CLASS char(254), MANUFCT char(20), INSTDATE date, ASBUILT char(30), SCHEME char(254), DATA_SRC char(20), COMMENTS char(254), ADDDBY char(20), ADDDTTM date, MODBY char(20), MODDTTM date, CONFIDENCE char(10), CRITICALITY double, ALLOCATE range_domain(ALLOCATE_4:integer:0:100), OLDGUID char(40), GlobalID globalid, created_user char(255), created_date date,
      last_edited_user char(255), last_edited_date date, SHAPE.STLength() double
    -> LineOnAreaOverlayer [LINE]
